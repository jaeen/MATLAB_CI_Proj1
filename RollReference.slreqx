# RollReference

## 1.3: Roll Hold Reference (Functional)
Describes the function for determining the roll reference angle.

### 1.3.1: Set roll hold reference angle to actual roll angle (Functional)
When roll hold mode becomes the active mode, the roll hold reference shall be set to the actual roll angle of the aircraft, except under the conditions described in the child requirements.
- Rationale: When engaging the mode at a small bank angle, it is assumed that the pilot wants to maintain level flight. When the mode is engaged above the autopilot roll limit, the autopilot should control to the limit. The turn knob will be considered to be in dent when it is less than 3 degrees.

#### 1.3.1.1: phiref = 0 if phi < 6 (Functional)
The roll hold reference shall be set to zero if the actual roll angle is less than 6 degrees, in either direction, at the time of roll hold engagement.

#### 1.3.1.2: phiref = 30 if phi > 30 (Functional)
The roll hold reference shall be set to 30 degrees in the same direction as the actual roll angle if the actual roll angle is greater than 30 degrees at the time of roll hold engagement.

#### 1.3.1.3: phiref = tk if tk >= 3 (Functional)
The roll reference shall be set to the cockpit turn knob command, up to a 30 degree limit, if the turn knob is commanding 3 degrees or more in either direction.
